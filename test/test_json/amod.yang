module amod {
  namespace "http://example.com/a";
  prefix a;

  import ietf-netconf {
    prefix nc;
  }

  include asub;

  description "Unicode test: Møøse once bit my sister";

  feature abc;

  identity bogus;

  identity foo {
    base bogus;
  }

  identity bar {
    base bogus;
  }

  typedef foo-ref {
    type leafref {
      path "/a:top/a:foo";
    }
  }

  container top {

    typedef bool {
      type union {
        type boolean;
        type uint8 {
          range "0|1";
        }
        type enumeration {
          enum "yes";
          enum "no";
        }
      }
    }
    leaf foo {
      type int64;
      default "-1";
    }
    leaf session-id {
      type nc:session-id-or-zero-type;
      mandatory false;
      description
        "Identifier of the session.
         A NETCONF session MUST be identified by a non-zero value.
         A non-NETCONF session MAY be identified by the value zero.";
    }
    leaf-list pac {
      type bool;
    }
    leaf bar {
      type empty;
    }
    leaf-list baz {
      type decimal64 {
        fraction-digits 18;
      }
    }
    leaf mek {
      type foo-ref;
    }
    anyxml junk;
    choice ch {
      case ca1 {
        leaf e {
          type empty;
        }
      }
    }
  }
}
