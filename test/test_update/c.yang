module c {
  namespace urn:c;
  prefix c;

  import b {
    prefix b;
  }

  revision 2014-03-01;

  augment /b:b {
    leaf foo {
      type int32;
      description "Unicode test: Møøse once bit my sister";
    }
  }

  container c {
    leaf q {
      type string;
    }
  }
}
