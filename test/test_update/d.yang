module d {
  namespace urn:d;
  prefix d;

  import c {
    prefix c;
    revision-date 2014-03-01;
  }

  description "Unicode test: Møøse once bit my sister";

  revision 2014-03-01;

  deviation /c:c/c:q {
    deviate add {
      default 'dummy';
    }
  }
}
